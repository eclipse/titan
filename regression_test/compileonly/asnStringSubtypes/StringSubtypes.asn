--/////////////////////////////////////////////////////////////////////////////
-- Copyright (c) 2000-2017 Ericsson Telecom AB
-- All rights reserved. This program and the accompanying materials
-- are made available under the terms of the Eclipse Public License v1.0
-- which accompanies this distribution, and is available at
-- http://www.eclipse.org/legal/epl-v10.html
--
-- Contributors:
--   Baranyi, Botond
--
--/////////////////////////////////////////////////////////////////////////////

StringSubtypes
DEFINITIONS

AUTOMATIC TAGS

::=

BEGIN

IMPORTS ; -- nothing


-- Types

TeletexStringRestricted ::= TeletexString (SIZE(4))

VideotexStringRestricted ::= VideotexString (SIZE(1..10))

GraphicStringRestricted ::= GraphicString (SIZE(0..3))

T61StringRestricted ::= T61String (SIZE(5))

GeneralStringRestricted ::= GeneralString (SIZE(1))


-- Values

val T61StringRestricted ::= "abcde"

END
